-- **********************************************************
-- Copyright 2010 VMware, Inc.  All rights reserved. 
-- **********************************************************

VMWARE-CIMOM-MIB DEFINITIONS ::= BEGIN

    IMPORTS
        MODULE-IDENTITY, NOTIFICATION-TYPE
    FROM SNMPv2-SMI
        MODULE-COMPLIANCE, NOTIFICATION-GROUP
    FROM SNMPv2-CONF
        vmwEnvCIM,vmwEnvIndicationTime
    FROM VMWARE-ENV-MIB
        vmwProductSpecific
    FROM VMWARE-ROOT-MIB;
  
    vmwCIMOMMIB MODULE-IDENTITY
    LAST-UPDATED "201008200000Z"
    ORGANIZATION "VMware, Inc"
    CONTACT-INFO
    "VMware, Inc
    3401 Hillview Ave
    Palo Alto, CA 94304
    Tel: 1-877-486-9273 or 650-427-5000
    Fax: 650-427-5001
    Web: http://communities.vmware.com/community/developer/forums/managementapi
    "
DESCRIPTION
     "This MIB module provides instrumentation of a CIM Object Manager." 
REVISION      "201008200000Z"
DESCRIPTION
     "Information on a CIM object manager subsystem."
::= { vmwCimOm 10 }

vmwCimOm OBJECT IDENTIFIER
    ::= { vmwProductSpecific 90 }

vmwCimOmNotifications OBJECT IDENTIFIER 
    ::= {vmwCimOm 0 }

vmwCimOmHeartbeat NOTIFICATION-TYPE
    OBJECTS     { vmwEnvIndicationTime }
    STATUS      current 
    DESCRIPTION
        "This notification, if the agent is so configured, will be sent 
         on a periodic basis to indicate cimom indication delivery is functioning."
    ::= { vmwCimOmNotifications 401 }

-- conformance information
vmwCimOmMIBConformance
OBJECT IDENTIFIER ::= { vmwCimOm 2 }
vmwCimOmMIBCompliances
OBJECT IDENTIFIER ::= { vmwCimOmMIBConformance 1 }
vmwCimOmMIBGroups  OBJECT IDENTIFIER ::= { vmwCimOmMIBConformance 2 }

-- compliance statements

vmwCimOmMIBBasicCompliance MODULE-COMPLIANCE
STATUS  current
DESCRIPTION
    "The compliance statement for entities which implement the 
    VMWARE-CIMOM-MIB."
MODULE  -- this module
MANDATORY-GROUPS { vmwCimOmNotificationGroup }
GROUP  vmwCimOmNotificationGroup
DESCRIPTION
    "This group is mandatory for systems with CIM object manager."
::= { vmwCimOmMIBCompliances 4 }

vmwCimOmNotificationGroup NOTIFICATION-GROUP
       NOTIFICATIONS {
       vmwCimOmHeartbeat
       }
       STATUS      current
       DESCRIPTION
           "Notifications related to CIM Object Manager subsystem."
       ::= { vmwCimOmMIBGroups 2 }


END
