-- --------------------------------------------------------------------
-- ************************ SECURITY GROUP ****************************
-- --------------------------------------------------------------------

-- ----------------------------------------
-- SECURITY ENABLE TABLE
-- ----------------------------------------
A3COM0008-SECURITY DEFINITIONS ::= BEGIN


   IMPORTS
      security FROM A3COM0004-GENERIC
      DisplayString FROM RFC1213-MIB
      OBJECT-TYPE FROM RFC-1212
      ;

securityEnableTable OBJECT-TYPE
   SYNTAX   SEQUENCE OF SecurityEnableTableEntry
   ACCESS   not-accessible
   STATUS   mandatory
   DESCRIPTION "A table of permissions for access to the managed device from 
   each of its interfaces, at each security access level. The table is fixed at 5 
   rows, indexed by the access level."
   ::= {security 1}

securityEnableTableEntry OBJECT-TYPE
   SYNTAX   SecurityEnableTableEntry
   ACCESS   not-accessible
   STATUS   mandatory
   DESCRIPTION "This table allows individual interfaces to be enabled or 
   disabled separately for each security level."
   INDEX {securityLevel}
   ::= {securityEnableTable 1}

SecurityEnableTableEntry ::= SEQUENCE {
      securityLevel     INTEGER,
      securityCommunityEnable    INTEGER,
      securitySecureEnable    INTEGER,
      securityTermEnable      INTEGER,
      securityTelnetEnable    INTEGER,
      securityFrontPanelEnable      INTEGER
      }

securityLevel OBJECT-TYPE
   SYNTAX   INTEGER  {
      monitor (1),
      secureMonitor (2),
      manager (3),
      specialist (4),
      security (5)
   }
   ACCESS   read-only
   STATUS   mandatory
   DESCRIPTION "Index to the security enable table."
   ::= {securityEnableTableEntry 1}

securityCommunityEnable OBJECT-TYPE
   SYNTAX   INTEGER  {
      enable (1),
      disable (2),
      permanentlyEnabled (3),
      permanentlyDisabled (4)
   }
   ACCESS   read-write
   STATUS   mandatory
   DESCRIPTION "Community SNMP access permission"
   ::= {securityEnableTableEntry 2}

securitySecureEnable OBJECT-TYPE
   SYNTAX   INTEGER  {
      enable (1),
      disable (2),
      permanentlyEnabled (3),
      permanentlyDisabled (4)
   }
   ACCESS   read-write
   STATUS   mandatory
   DESCRIPTION "Secure SNMP access permission"
   ::= {securityEnableTableEntry 3}

securityTermEnable OBJECT-TYPE
   SYNTAX   INTEGER  {
      enable (1),
      disable (2),
      permanentlyEnabled (3),
      permanentlyDisabled (4)
   }
   ACCESS   read-write
   STATUS   mandatory
   DESCRIPTION "Local Terminal access permission"
   ::= {securityEnableTableEntry 4}

securityTelnetEnable OBJECT-TYPE
   SYNTAX   INTEGER  {
      enable (1),
      disable (2),
      permanentlyEnabled (3),
      permanentlyDisabled (4)
   }
   ACCESS   read-write
   STATUS   mandatory
   DESCRIPTION "Telnet access permission"
   ::= {securityEnableTableEntry 5}

securityFrontPanelEnable OBJECT-TYPE
   SYNTAX   INTEGER  {
      enable (1),
      disable (2),
      permanentlyEnabled (3),
      permanentlyDisabled (4)
   }
   ACCESS   read-write
   STATUS   mandatory
   DESCRIPTION "Front Panel access permission"
   ::= {securityEnableTableEntry 6}

-- ----------------------------------------
-- The Local device USER TABLE
-- ----------------------------------------
securityUserTable OBJECT-TYPE
   SYNTAX   SEQUENCE OF SecurityUserTableEntry
   ACCESS   not-accessible
   STATUS   mandatory
   DESCRIPTION "A table used to define Users. Users can be created/modified 
   or deleted, with the exception of the default Users which cannot be deleted."
   ::= {security 2}

securityUserTableEntry OBJECT-TYPE
   SYNTAX   SecurityUserTableEntry
   ACCESS   not-accessible
   STATUS   mandatory
   DESCRIPTION "1. Creating a new user is done by using the username as a 
   qualifier and SETting any of the items in the row - defaults will be used for 
   the remaining values. 2. Deleting a user is by writing 'invalid' to the status 
   column. 3. There must always be users called 'monitor', 'manager' and 'security' 
   - these cannot be deleted."
   INDEX {securityUserName}
   ::= {securityUserTable 1}

SecurityUserTableEntry ::= SEQUENCE {
      securityUserStatus      INTEGER,
      securityUserName     DisplayString (SIZE(1..10)),
      securityUserLevel    INTEGER,
      securityUserPassword    DisplayString (SIZE(0..10)),
      securityUserCommunity      DisplayString (SIZE(0..32)),
      securityUserLocParty    OBJECT IDENTIFIER,
      securityUserMgrParty    OBJECT IDENTIFIER
      }

securityUserStatus OBJECT-TYPE
   SYNTAX   INTEGER  {
      valid (1),
      invalid (2)
   }
   ACCESS   read-write
   STATUS   mandatory
   DESCRIPTION "User Status.  `invalid' is used to indicate this user is no 
   longer allowed to access this device, and the table entry may subsequently be 
   re-used. Note that the Status of default Users cannot be set to invalid."
   ::= {securityUserTableEntry 1}

securityUserName OBJECT-TYPE
   SYNTAX   DisplayString (SIZE(1..10))
   ACCESS   read-only
   STATUS   mandatory
   DESCRIPTION "An ASCII string for the User Name.  Empty strings are not 
   allowed.  The index column for the User Table."
   ::= {securityUserTableEntry 2}

securityUserLevel OBJECT-TYPE
   SYNTAX   INTEGER  {
      monitor (1),
      secureMonitor (2),
      manager (3),
      specialist (4),
      security (5)
   }
   ACCESS   read-write
   STATUS   mandatory
   DESCRIPTION "User Access Level defining the scope of management allowed 
   for this user.  Note that the access level of default Users cannot be changed."
   ::= {securityUserTableEntry 3}

securityUserPassword OBJECT-TYPE
   SYNTAX   DisplayString (SIZE(0..10))
   ACCESS   write-only
   STATUS   mandatory
   DESCRIPTION "The password required for user confirmation, when access is 
   made via the local serial port, the front panel, or via Telnet."
   ::= {securityUserTableEntry 4}

securityUserCommunity OBJECT-TYPE
   SYNTAX   DisplayString (SIZE(0..32))
   ACCESS   read-write
   STATUS   mandatory
   DESCRIPTION "The community string identifying this user, when access is 
   made via the original community-based SNMP (RFC1157)."
   ::= {securityUserTableEntry 5}

securityUserLocParty OBJECT-TYPE
   SYNTAX   OBJECT IDENTIFIER
   ACCESS   read-write
   STATUS   mandatory
   DESCRIPTION "The local party identity of this user, when access is made 
   via secure SNMP."
   ::= {securityUserTableEntry 6}

securityUserMgrParty OBJECT-TYPE
   SYNTAX   OBJECT IDENTIFIER
   ACCESS   read-write
   STATUS   mandatory
   DESCRIPTION "The manager party identity for this user, when access is 
   made via secure SNMP."
   ::= {securityUserTableEntry 7}

-- 
-- ----------------------------------------
-- AUDIT LOG
-- ----------------------------------------
securityAuditLogTable OBJECT-TYPE
   SYNTAX   SEQUENCE OF SecurityAuditLogEntry
   ACCESS   not-accessible
   STATUS   mandatory
   DESCRIPTION "The audit log is a circular table recording all updates to 
   the managed database on the device.  The log must be read regularly by a 
   management device, to maintain a more permanent record of the management history."
   ::= {security 3}

securityAuditLogEntry OBJECT-TYPE
   SYNTAX   SecurityAuditLogEntry
   ACCESS   not-accessible
   STATUS   mandatory
   DESCRIPTION "Each entry contains the time an update was made, by whom, 
   the item referenced, the new value and the result of this request."
   INDEX {securityAuditIndex}
   ::= {securityAuditLogTable 1}

SecurityAuditLogEntry ::= SEQUENCE {
      securityAuditIndex      INTEGER,
      securityAuditTime    TimeTicks,
      securityAuditUser    DisplayString (SIZE(0..10)),
      securityAuditObject     OBJECT IDENTIFIER,
      securityAuditValue      OCTET STRING,
      securityAuditResult     INTEGER
      }

securityAuditIndex OBJECT-TYPE
   SYNTAX   INTEGER (1..65535)
   ACCESS   read-only
   STATUS   mandatory
   DESCRIPTION "Audit Log Index.  A monotonically increasing value to 
   uniquely identify an entry in the audit log.  This value wraps around (to 1) 
   after reaching the maximum value (65535)."
   ::= {securityAuditLogEntry 1}

securityAuditTime OBJECT-TYPE
   SYNTAX   TimeTicks 
   ACCESS   read-only
   STATUS   mandatory
   DESCRIPTION "The time, in hundredths of a second since the last system 
   restart, of the update request."
   ::= {securityAuditLogEntry 2}

securityAuditUser OBJECT-TYPE
   SYNTAX   DisplayString (SIZE(0..10))
   ACCESS   read-only
   STATUS   mandatory
   DESCRIPTION "The name of the user making the request."
   ::= {securityAuditLogEntry 3}

securityAuditObject OBJECT-TYPE
   SYNTAX   OBJECT IDENTIFIER
   ACCESS   read-only
   STATUS   mandatory
   DESCRIPTION "The object identifier of the item being updated.  This 
   includes any qualifier for the item."
   ::= {securityAuditLogEntry 4}

securityAuditValue OBJECT-TYPE
   SYNTAX   OCTET STRING  (SIZE(0..200))
   ACCESS   read-only
   STATUS   mandatory
   DESCRIPTION "The new value for the item."
   ::= {securityAuditLogEntry 5}

securityAuditResult OBJECT-TYPE
   SYNTAX   INTEGER  {
      pending (1),
      too-big (2),
      failed (3),
      locked (4),
      security-violation (5),
      no-such-function (6),
      no-such-item (7),
      noResource (8),
      notRegistered (9),
      keyViolation (10),
      badValue (11),
      success (255)
   }
   ACCESS   read-only
   STATUS   mandatory
   DESCRIPTION "The result of the update request may indicate that it was 
   applied successfully, that it failed (for one of a number of reasons) or that it 
   is still in progress."
   ::= {securityAuditLogEntry 6}



END
