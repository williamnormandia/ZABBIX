-- **********************************************************************
--
-- Name:	3Com SuperStack II Stack Unit Types & Identifiers
-- 
-- Description: 
--  
--
-- History  Date        Reason for Change
--
-- 1.00     1997       	Issued as 3Com RFC.
-- 1.01     11 Sep 97	Rename Hub110 to Dual Speed Hub 500
-- 1.02      7 April 98	Add descriptions for the various products
-- 1.03     26 May 98	Add sysObjID for stackSwitch3400 (popadom)
-- 1.04     18 Aug 98	Add unitTypes for stackSwitch3400 (popadom)
-- 1.05     19 Jan 99	Add sysObjID, unitTypes for stackSwitchMadras
--			This will be renamed when a product name is assigned.
-- 1.06     28 Jan 99	Add sysObjID, unitTypes for stackSwitchGerry
--			This will be renamed when a product name is assigned.
-- 1.07     19 Feb 99	Add sysObjID, unitTypes for stackSwitchBeefy
--			This will be renamed when a product name is assigned.
-- 1.08     16 Mar 99	Add sysObjID, unitTypes for stackSwitchAsterix
--			This will be renamed when a product name is assigned.
-- 
--
-- **********************************************************************
-- Copyright (c) 3Com Technologies. (1996-1999)
-- **********************************************************************

A3COM0025-STACK-UNIT-TYPES DEFINITIONS ::= BEGIN


   IMPORTS
      stackSysObjIdentities, stackUnitTypes FROM A3COM0017-STACK-CONFIG
      OBJECT-TYPE FROM RFC-1212
      ;

-- Define all possible sysObjIdent values as a branch from this MIB. Note that to
-- allow dumb management applications to distinguish between different products we
-- are going to allocate a different sysObjID to each product category (but not
-- different port configurations etc). This allocation will be hierarchical so
-- where necessary we can have a family ID then a sub-family value.

-- Note that for historical reasons the PSHub40 and PSHub50 will use the
-- root of this tree, that is the sysObjId for these products will be
--
-- NOTE ALSO THAT ALL 3COM APPLICATIONS SHOULD DO A PARTIAL MATCH ON sysObjId
-- AGAINST stackDistributedAgent. ALL CHILDREN OF THESE VALUES SHOULD BE
-- TREATED AS SSII DISTRIBUTED AGENTS AND APPLICATIONS SHOULD BASE
-- AGENT CAPABILITIES ON THE ACTUAL VALUE READ. INSTEAD APPLICATIONS SHOULD
-- USE THE CONTENTS OF THE STACK CONFIGURATION MIB, AGENT CAPABILITIES
-- VALUE TO DETERMINE WHAT THE AGENT CAN DO!
-- stackDistributedAgent.
stackDistributedAgent             OBJECT IDENTIFIER ::= {stackSysObjIdentities 1}

stackHub                          OBJECT IDENTIFIER ::= {stackDistributedAgent 1}
stackDualSpeedHub500              OBJECT IDENTIFIER ::= {stackHub 1}
stackSwitch                       OBJECT IDENTIFIER ::= {stackDistributedAgent 2}
stackSwitch1100                   OBJECT IDENTIFIER ::= {stackSwitch 1}
stackSwitch3300                   OBJECT IDENTIFIER ::= {stackSwitch 2}
stackSwitch3400                   OBJECT IDENTIFIER ::= {stackSwitch 3}
stackSwitchMadras                 OBJECT IDENTIFIER ::= {stackSwitch 4}
stackSwitchGerry                  OBJECT IDENTIFIER ::= {stackSwitch 5}
stackSwitchBeefy                  OBJECT IDENTIFIER ::= {stackSwitch 6}
stackSwitchAsterix                OBJECT IDENTIFIER ::= {stackSwitch 7}

-- The stackUnitType is an integer id which applications can use to distinguish
-- between different hardware devices in a stack. In order to administer these
-- values the integer will be defined as the last level in an OID. The values
-- are defined below. Note that these id's will also be used for other MIBs
-- which require an OID to identify a unit type. For example rptrGroupObjectID.

-- PSHub 40
stack12Port10BaseTRepeater        OBJECT IDENTIFIER ::= {stackUnitTypes 1}
stack24Port10BaseTRepeater        OBJECT IDENTIFIER ::= {stackUnitTypes 2}

-- PSHub 50
stack24Port10BaseTRepeaterSwitch  OBJECT IDENTIFIER ::= {stackUnitTypes 3}

-- Dual Speed Hub 500
stack12Port100BaseTxRepeater      OBJECT IDENTIFIER ::= {stackUnitTypes 4}
stack24Port100BaseTxRepeater      OBJECT IDENTIFIER ::= {stackUnitTypes 5}
stack12Port10100BaseTxRepeater    OBJECT IDENTIFIER ::= {stackUnitTypes 6}
stack24Port10100BaseTxRepeater    OBJECT IDENTIFIER ::= {stackUnitTypes 7}

-- Switch 1100
stack12Port10BaseTSwitch          OBJECT IDENTIFIER ::= {stackUnitTypes 8}
stack24Port10BaseTSwitch          OBJECT IDENTIFIER ::= {stackUnitTypes 9}

-- Switch 3300
stack12Port10100BaseTxSwitch      OBJECT IDENTIFIER ::= {stackUnitTypes 10}
stack24Port10100BaseTxSwitch      OBJECT IDENTIFIER ::= {stackUnitTypes 11}

-- Switch 610a Fixed Configuration
stack24Port10BaseTFixedSwitch     OBJECT IDENTIFIER ::= {stackUnitTypes 12}

-- Switch 630a Fixed Configuration 
stack24Port10100BaseTxFixedSwitch OBJECT IDENTIFIER ::= {stackUnitTypes 13}

-- Switch 3300
stack8Port100BaseFXSwitch         OBJECT IDENTIFIER ::= {stackUnitTypes 14}

-- Switch 3400
stack12Port10100BaseTxSwitch2     OBJECT IDENTIFIER ::= {stackUnitTypes 15}
stack24Port10100BaseTxSwitch2     OBJECT IDENTIFIER ::= {stackUnitTypes 16}

-- Switch Madras
stack12Port10100BaseTxSwitch3     OBJECT IDENTIFIER ::= {stackUnitTypes 17}
stack24Port10100BaseTxSwitch3     OBJECT IDENTIFIER ::= {stackUnitTypes 18}

-- Switch Gerry
stack12Port1001000BaseTxSwitch    OBJECT IDENTIFIER ::= {stackUnitTypes 19}

-- Switch Beefy
stack12Port10100BaseTxSwitch4     OBJECT IDENTIFIER ::= {stackUnitTypes 20}
stack24Port10100BaseTxSwitch4     OBJECT IDENTIFIER ::= {stackUnitTypes 21}

-- Wireless Asterix
stack10BaseT1Radio                OBJECT IDENTIFIER ::= {stackUnitTypes 22}
stack10BaseT4Radio                OBJECT IDENTIFIER ::= {stackUnitTypes 23}


END
