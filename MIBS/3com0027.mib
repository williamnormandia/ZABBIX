A3COM0027-RMON-EXTENSIONS DEFINITIONS ::= BEGIN


	IMPORTS
		OBJECT-TYPE FROM RFC-1212
		TRAP-TYPE FROM RFC-1215
		rmonExtensions FROM A3COM0004-GENERIC
		;

remotePoll        OBJECT IDENTIFIER ::= {rmonExtensions 1}
-- 3Com RFC 0019
hostExtensions    OBJECT IDENTIFIER ::= {rmonExtensions 2}
alarmExtensions   OBJECT IDENTIFIER ::= {rmonExtensions 3}
eventExtensions   OBJECT IDENTIFIER ::= {rmonExtensions 4}
-- 3Com RFC 0024
command           OBJECT IDENTIFIER ::= {rmonExtensions 5}
-- Root of A3COM0034-PROBECONFIG-EXTENSION.
probeConfigNetExtensions  OBJECT IDENTIFIER ::= {rmonExtensions 6}


END
