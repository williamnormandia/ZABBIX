--  **********************************************************************************
--
--              Windows Operating System Management Functions
--         Management Information Base for SNMP Network Management
--
--
--      Copyright 2002,2003 Hewlett-Packard Development Company, L.P.
--
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
-- ***********************************************************************************

CPQOS-MIB DEFINITIONS ::= BEGIN

    IMPORTS
        compaq                  FROM CPQHOST-MIB
        DisplayString           FROM RFC1213-MIB
        OBJECT-TYPE             FROM RFC-1212
        TRAP-TYPE               FROM RFC-1215
        sysName                 FROM RFC1213-MIB
        cpqHoTrapFlags          FROM CPQHOST-MIB;

--  compaq                 OBJECT IDENTIFIER ::= { enterprises 232 }
    cpqWinOsMgmt           OBJECT IDENTIFIER ::= { compaq 19 }

    cpqOsMibRev            OBJECT IDENTIFIER ::= { cpqWinOsMgmt 1 }
    cpqOsComponent         OBJECT IDENTIFIER ::= { cpqWinOsMgmt 2 }

    cpqOsInterface         OBJECT IDENTIFIER ::= { cpqOsComponent 1 }
    cpqOsSystem            OBJECT IDENTIFIER ::= { cpqOsComponent 2 }
    cpqOsProcessor         OBJECT IDENTIFIER ::= { cpqOsComponent 3 }
    cpqOsMemory            OBJECT IDENTIFIER ::= { cpqOsComponent 4 }
    cpqOsCache             OBJECT IDENTIFIER ::= { cpqOsComponent 5 }
    cpqOsPagingFile        OBJECT IDENTIFIER ::= { cpqOsComponent 6 }
    cpqOsPhysicalDisk      OBJECT IDENTIFIER ::= { cpqOsComponent 7 }
    cpqOsLogicalDisk       OBJECT IDENTIFIER ::= { cpqOsComponent 8 }
    cpqOsServer            OBJECT IDENTIFIER ::= { cpqOsComponent 9 }
    cpqOsNetworkInterface  OBJECT IDENTIFIER ::= { cpqOsComponent 10 }
    cpqOsTcp               OBJECT IDENTIFIER ::= { cpqOsComponent 11 }
    cpqOsProcess           OBJECT IDENTIFIER ::= { cpqOsComponent 12 }

    cpqOsCommon            OBJECT IDENTIFIER ::= { cpqOsInterface 4 }

-- ***********************************************************************************
--   Operating System Information MIB Revision
--   =========================================
--
-- The compaq enterprise        (1.3.6.1.4.1.232)
--      cpqWinOsMgmt Group      (1.3.6.1.4.1.232.19)
--       cpqOsMibRev Group      (1.3.6.1.4.1.232.19.1)
--
--
--      An SNMP agent conforming to this document will return a
--      cpqOsMibRevMajor of one (1) and a cpqOsMibRevMinor of four (4).
--
--      Implementation of the MibRev group is mandatory for all agents
--      supporting the Windows Operating System Management MIB.
--
-- ***********************************************************************************

    cpqOsMibRevMajor OBJECT-TYPE
        SYNTAX  INTEGER (1..65535)
        ACCESS  read-only
        STATUS  mandatory
        DESCRIPTION
            "The Major Revision level of the MIB.

            A change in the major revision level represents a major change
            in the architecture of the MIB.  A change in the major revision
            level may indicate a significant change in the information
            supported and/or the meaning of the supported information,
            correct interpretation of data may require a MIB document with
            the same major revision level."
        ::= { cpqOsMibRev 1 }

    cpqOsMibRevMinor OBJECT-TYPE
        SYNTAX  INTEGER (0..65535)
        ACCESS  read-only
        STATUS  mandatory
        DESCRIPTION
            "The Minor Revision level of the MIB.

            A change in the minor revision level may represent some minor
            additional support, no changes to any pre-existing information
            has occurred."
        ::= { cpqOsMibRev 2 }

    cpqOsMibCondition OBJECT-TYPE
        SYNTAX  INTEGER {
            other(1),
            ok(2),              -- default
            degraded(3),
            failed(4)
            }
        ACCESS  read-only
        STATUS  mandatory
        DESCRIPTION
            "The overall condition.

             This object represents the overall status of the Operating
             System management system represented by this MIB."
        ::= { cpqOsMibRev 3 }

-- ***********************************************************************************
--   Operating System MIB OS Common Group
--   ====================================
--
-- The compaq enterprise               (1.3.6.1.4.1.232)
--      cpqWinOsMgmt Group             (1.3.6.1.4.1.232.19)
--       cpqOsComponent Group          (1.3.6.1.4.1.232.19.2)
--        cpqOsInterface Group         (1.3.6.1.4.1.232.19.2.1)
--         cpqOsCommon Group           (1.3.6.1.4.1.232.19.2.1.4)
--
--
--  Implementation of the cpqOsCommon group is mandatory for all
--  Agents that support the Windows OS Management MIB.
--
-- ***********************************************************************************

    cpqOsCommonPollFreq OBJECT-TYPE
        SYNTAX  INTEGER (0..65535)
        ACCESS  read-write
        STATUS  mandatory
        DESCRIPTION
            "The Management Agent's polling frequency.

            The frequency, in seconds, at which the Agent requests
            information from the device driver.  A frequency of zero (0)
            indicates that the Insight Agent retrieves the information upon
            request of a management station, it does not poll the device
            driver at a specific interval.

            If the poll frequency is zero (0) all attempts to write to this
            object will fail.  If the poll frequency is non-zero,
            setting this value will change the polling frequency of the
            Insight Agent.  Setting the poll frequency to zero (0) will
            always fail, an agent may also choose to fail any request to
            change the poll frequency to a value that would severely impact
            system performance."
        ::= { cpqOsCommon 1 }

-- ***********************************************************************************
--   Operating System MIB Operating System Group
--   ===========================================
--
-- The compaq enterprise               (1.3.6.1.4.1.232)
--      cpqWinOsMgmt Group             (1.3.6.1.4.1.232.19)
--       cpqOsComponent Group          (1.3.6.1.4.1.232.19.2)
--        cpqOsSystem Group            (1.3.6.1.4.1.232.19.2.2)
--
--  The cpqOsSystem group describes the Operating Systems Performance properties.
--
-- ***********************************************************************************

    cpqOsSystemStatus OBJECT-TYPE
        SYNTAX  INTEGER {
            other(1),
            ok(2),
            degraded(3),
            failed(4)
            }
        ACCESS  read-only
        STATUS  mandatory
        DESCRIPTION
            "This value specifies the overall condition of the System Object."
        ::= { cpqOsSystem 1 }

    cpqOsSystemUpTime OBJECT-TYPE
        SYNTAX  DisplayString (SIZE (0..64))
        ACCESS  read-only
        STATUS  mandatory
        DESCRIPTION
            "Total Time that the computer has been operational since it was
            last started."
        ::= { cpqOsSystem 2 }

    cpqOsSystemThreads OBJECT-TYPE
        SYNTAX  INTEGER
        ACCESS  read-only
        STATUS  mandatory
        DESCRIPTION
            "Threads is the number of threads in the computer at the time of data
            collection. Notice that this is an instantaneous count, not an average
            over the time interval. A thread is the basic executable entity that can
            execute instructions in a processor."

        ::= { cpqOsSystem 3 }

    cpqOsSysContextSwitchesPersec OBJECT-TYPE
        SYNTAX  INTEGER
        ACCESS  read-only
        STATUS  mandatory
        DESCRIPTION
            "Context Switches/sec is the combined rate at which all processors on the
            computer are switched from one thread to another. Context switches occur
            when a running thread voluntarily relinquishes the processor, is preempted
            by a higher priority ready thread, or switches between user-mode and
            privileged (kernel) mode to use an Executive or subsystem service. It is
            the sum of Thread: Context Switches/sec for all threads running on all
            processors in the computer and is measured in numbers of switches. There
            are context switch counters on the System and Thread objects."
        ::= { cpqOsSystem 4 }

    cpqOsSysCpuQueueLength OBJECT-TYPE
        SYNTAX  INTEGER
        ACCESS  read-only
        STATUS  mandatory
        DESCRIPTION
            "Processor Queue Length is the number of threads in the processor queue.
            There is a single queue for processor time even on computers with multiple
            processors. Unlike the disk counters, this counter counts ready threads
            only, not threads that are running. A sustained processor queue of greater
            than two threads generally indicates processor congestion."
        ::= { cpqOsSystem 5 }

    cpqOsSysProcesses OBJECT-TYPE
        SYNTAX  INTEGER
        ACCESS  read-only
        STATUS  mandatory
        DESCRIPTION
            "Processes is the number of processes in the computer at the time of data
            collection. Notice that this is an instantaneous count, not an average
            over the time interval. Each process represents the running of a program."
        ::= { cpqOsSystem 6 }

    cpqOsSysRegistryInUsePercent OBJECT-TYPE
        SYNTAX  INTEGER
        ACCESS  read-only
        STATUS  mandatory
        DESCRIPTION
            "RegistryInUsePercent is the percentage of the Total Registry Quota
            Allowed that is currently being used by the system.  This counter
            displays the current percentage value only; it is not an average."
        ::= { cpqOsSystem 7 }

-- ***********************************************************************************
--   Operating System MIB Processor Group
--   ====================================
--
-- The compaq enterprise               (1.3.6.1.4.1.232)
--      cpqWinOsMgmt Group             (1.3.6.1.4.1.232.19)
--       cpqOsComponent Group          (1.3.6.1.4.1.232.19.2)
--        cpqOsProcessor Group         (1.3.6.1.4.1.232.19.2.3)
--         cpqOsProcessorTable         (1.3.6.1.4.1.232.19.2.3.2)
--
--  The cpqOsProcessor group describes the Processors Performance properties.
--
-- ***********************************************************************************

    cpqOsProcessorStatus OBJECT-TYPE
        SYNTAX  INTEGER {
            other(1),
            ok(2),
            degraded(3),
            failed(4)
            }
        ACCESS  read-only
        STATUS  mandatory
        DESCRIPTION
            "This value specifies the overall condition of Processor Object
            instances."
        ::= { cpqOsProcessor 1 }

    cpqOsProcessorTable OBJECT-TYPE
        SYNTAX  SEQUENCE OF CpqOsProcessorEntry
        ACCESS  not-accessible
        STATUS  mandatory
        DESCRIPTION
            "A table of Processor Entries."
        ::= { cpqOsProcessor 2 }

    cpqOsProcessorEntry OBJECT-TYPE
        SYNTAX  CpqOsProcessorEntry
        ACCESS  not-accessible
        STATUS  mandatory
        DESCRIPTION
            "A Processor Entry."
        INDEX   { cpqOsCpuIndex }
        ::= { cpqOsProcessorTable 1 }

        CpqOsProcessorEntry ::= SEQUENCE {
            cpqOsCpuIndex                  INTEGER,
            cpqOsCpuInstance               DisplayString,
            cpqOsCpuInterruptsPerSec       INTEGER,
            cpqOsCpuTimePercent            INTEGER,
            cpqOsWarCpuTimePercent         INTEGER,
            cpqOsCriCpuTimePercent         INTEGER,
            cpqOsCpuUserTimePercent        INTEGER,
            cpqOsCpuPrivilegedTimePercent  INTEGER,
            cpqOsCpuCondition              INTEGER,
            cpqOsCpuPercentDPCTime         INTEGER,
            cpqOsCpuPercentInterruptTime   INTEGER
        }

    cpqOsCpuIndex OBJECT-TYPE
        SYNTAX  INTEGER
        ACCESS  read-only
        STATUS  mandatory
        DESCRIPTION
            "This Processor Instance number."
        ::= { cpqOsProcessorEntry 1 }

    cpqOsCpuInstance OBJECT-TYPE
        SYNTAX  DisplayString (SIZE (0..64))
        ACCESS  read-only
        STATUS  mandatory
        DESCRIPTION
            "This Processor Instance Name."
        ::= { cpqOsProcessorEntry 2 }

    cpqOsCpuInterruptsPerSec OBJECT-TYPE
        SYNTAX  INTEGER
        ACCESS  read-only
        STATUS  mandatory
        DESCRIPTION
            "Interrupts/sec is the average number of hardware interrupts the processor
            is receiving and servicing in each second. It does not include DPCs, which
            are counted separately. This value is an indirect indicator of the
            activity of devices that generate interrupts, such as the system clock,
            the mouse, disk drivers, data communication lines, network interface cards
            and other peripheral devices. These devices normally interrupt the
            processor when they have completed a task or require attention. Normal
            thread execution is suspended during interrupts. Most system clocks
            interrupt the processor every 10 milliseconds, creating a background of
            interrupt activity."
        ::= { cpqOsProcessorEntry 3 }

    cpqOsCpuTimePercent OBJECT-TYPE
        SYNTAX  INTEGER
        ACCESS  read-only
        STATUS  mandatory
        DESCRIPTION
            "%Processor Time is the percentage of time that the processor is executing
            a non-Idle thread. This counter was designed as a primary indicator of
            processor activity. It is calculated by measuring the time that the
            processor spends executing the thread of the Idle process in each sample
            interval, and subtracting that value from 100%. (Each processor has an
            Idle thread which consumes cycles when no other threads are ready to run.)
            It can be viewed as the fraction of the time spent doing useful work."
        ::= { cpqOsProcessorEntry 4 }

    cpqOsWarCpuTimePercent OBJECT-TYPE
        SYNTAX  INTEGER
        ACCESS  read-write
        STATUS  mandatory
        DESCRIPTION
            "Warning alarm will be issued if,
              (cpqOsCpuTotalCpuTimePercent >= cpqOsWarCpuTotalCpuTimePercent  &&
               cpqOsCpuTotalCpuTimePercent < cpqOsCriCpuTotalCpuTimePercent)
            for 15 data collection intervals."
        ::= { cpqOsProcessorEntry 5 }

    cpqOsCriCpuTimePercent OBJECT-TYPE
        SYNTAX  INTEGER
        ACCESS  read-write
        STATUS  mandatory
        DESCRIPTION
            "Critical alarm will be issued if,
              (cpqOsCpuTotalCpuTimePercent >= cpqOsCriCpuTotalCpuTimePercent)
            for 15 data collection intervals."
        ::= { cpqOsProcessorEntry 6 }

    cpqOsCpuUserTimePercent OBJECT-TYPE
        SYNTAX  INTEGER
        ACCESS  read-only
        STATUS  mandatory
        DESCRIPTION
            "%User Time is the percentage of non-idle processor time spent in user
            mode. User mode is a restricted processing mode designed for applications,
            environment subsystems, and integral subsystems. The alternative,
            privileged mode, is designed for operating system components and allows
            direct access to hardware and all memory. The operating system switches
            application threads to privileged mode to obtain operating system
            services."

        ::= { cpqOsProcessorEntry 7 }

    cpqOsCpuPrivilegedTimePercent OBJECT-TYPE
        SYNTAX  INTEGER
        ACCESS  read-only
        STATUS  mandatory
        DESCRIPTION
            "%Privileged Time is the percentage of non-idle processor time spent in
            privileged mode. (Privileged mode is a processing mode designed for
            operating system components and hardware-manipulating drivers. It allows
            direct access to hardware and all memory. The alternative, user mode, is
            a restricted processing mode designed for applications, environment
            subsystems, and integral subsystems. The operating system switches
            application threads to privileged mode to obtain operating system
            services.) %Privileged Time includes time servicing interrupts and DPCs.
            A high rate of privileged time might be attributable to a large number
            of interrupts generated by a failing device."
        ::= { cpqOsProcessorEntry 8 }

    cpqOsCpuCondition OBJECT-TYPE
        SYNTAX  INTEGER {
            other(1),
            ok(2),
            degraded(3),
            failed(4)
            }
        ACCESS  read-only
        STATUS  mandatory
        DESCRIPTION
            "The condition of this Processor Object Instance."
        ::= { cpqOsProcessorEntry 9 }

    cpqOsCpuPercentDPCTime OBJECT-TYPE
        SYNTAX  INTEGER
        ACCESS  read-only
        STATUS  mandatory
        DESCRIPTION
            "% DPC Time is the percentage of time that the processor spent receiving
             and servicing deferred procedure calls (DPCs) during the sample interval.
             (DPCs are interrupts that run at a lower priority than standard interrupts).
             % DPC Time is a component of % Privileged Time because DPCs are executed in
             privileged mode. They are counted separately and are not a component of the
             interrupt counters. This counter displays the average busy time as a
             percentage of the sample time."
        ::= { cpqOsProcessorEntry 10 }

    cpqOsCpuPercentInterruptTime OBJECT-TYPE
        SYNTAX  INTEGER
        ACCESS  read-only
        STATUS  mandatory
        DESCRIPTION
            "% Interrupt Time is the percentage of time the processor spent receiving and
             servicing hardware interrupts during the sample interval.  This value is an
             indirect indicator of the activity of devices that generate interrupts, such
             as the system clock, the mouse, disk drivers, data communication lines,
             network interface cards and other peripheral devices. These devices normally
             interrupt the processor when they have completed a task or require attention.
             Normal thread execution is suspended during interrupts. Most system clocks
             interrupt the processor every 10 milliseconds, creating a background of
             interrupt activity. This counter displays the average busy time as a
             percentage of the sample time."
        ::= { cpqOsProcessorEntry 11 }

-- ***********************************************************************************
--   Operating System MIB Memory Group
--   =================================
--
-- The compaq enterprise               (1.3.6.1.4.1.232)
--      cpqWinOsMgmt Group             (1.3.6.1.4.1.232.19)
--       cpqOsComponent Group          (1.3.6.1.4.1.232.19.2)
--        cpqOsMemory Group            (1.3.6.1.4.1.232.19.2.4)
--
--  The cpqOsMemory group describes the System Memory Performance properties.
--
-- ***********************************************************************************

    cpqOsMemoryStatus OBJECT-TYPE
        SYNTAX  INTEGER {
            other(1),
            ok(2),
            degraded(3),
            failed(4)
            }
        ACCESS  read-only
        STATUS  mandatory
        DESCRIPTION
            "This value specifies the overall condition of Memory Object."
        ::= { cpqOsMemory 1 }

    cpqOsMemAvailableKBytes OBJECT-TYPE
        SYNTAX  INTEGER
        ACCESS  read-only
        STATUS  mandatory
        DESCRIPTION
            "Available KBytes is the amount of physical memory available to processes
            running on the computer, in KBytes. It is calculated by summing space on
            the Zeroed, Free, and Standby memory lists. Free memory is ready for use;
            Zeroed memory is pages of memory filled with zeros to prevent later
            processes from seeing data used by a previous process. Standby memory
            is memory removed from a process's working set (its physical memory) on
            route to disk, but is still available to be recalled."
        ::= { cpqOsMemory 2 }

    cpqOsMemPagesPerSec OBJECT-TYPE
        SYNTAX  INTEGER
        ACCESS  read-only
        STATUS  mandatory
        DESCRIPTION
            "Pages/sec is the number of pages read from or written to disk to
            resolve hard page faults. (Hard page faults occur when a process
            requires code or data that is not in its working set or elsewhere
            in physical memory, and must be retrieved from disk.) This counter
            was designed as a primary indicator of the kinds of faults that cause
            system-wide delays. It is the sum of Memory: Pages Input/sec and
            Memory: Pages Output/sec. It is counted in numbers of pages, so it can
            be compared to other counts of pages, such as Memory: Page Faults/sec,
            without conversion. It includes pages retrieved to satisfy faults in
            the file system cache (usually requested by applications) non-cached
            mapped memory files."
        ::= { cpqOsMemory 3 }

    cpqOsMemPagesInputPerSec OBJECT-TYPE
        SYNTAX  INTEGER
        ACCESS  read-only
        STATUS  mandatory
        DESCRIPTION
            "Pages Input/sec is the number of pages read from disk to resolve hard
            page faults. (Hard page faults occur when a process requires code or
            data that is not in its working set or elsewhere in physical memory,
            and must be retrieved from disk.) This counter was designed as a primary
            indicator of the kinds of faults that cause system-wide delays. It
            includes pages retrieved to satisfy faults in the file system cache
            (usually requested by applications) and in non-cached mapped memory
            files. This counter counts numbers of pages, and can be compared to other
            counts of pages, such as Memory: Page Faults/sec, without conversion."
        ::= { cpqOsMemory 4 }

    cpqOsMemPagesOutputPerSec OBJECT-TYPE
        SYNTAX  INTEGER
        ACCESS  read-only
        STATUS  mandatory
        DESCRIPTION
            "Pages Output/sec is the number of pages written to disk to free up space
            in physical memory. Pages are written back to disk only if they are
            changed in physical memory, so they are likely to hold data, not code.
            A high rate of pages output might indicate a memory shortage.  Windows
            NT writes more pages back to disk to free up space when physical memory is
            in short supply. This counter counts numbers of pages, and can be compared
            to other counts of pages, without conversion. This counter displays the
            difference between the values observed in the last two samples, divided by
            the duration of the sample interval."
        ::= { cpqOsMemory 5 }

    cpqOsMemPageFaultsPerSec OBJECT-TYPE
        SYNTAX  INTEGER
        ACCESS  read-only
        STATUS  mandatory
        DESCRIPTION
            "Page Faults/sec is overall rate at which of faulted pages are handled by
            the processor. It is measured in numbers of pages faulted. A page fault
            occurs when a process requires code or data that is not in its working set
            (its space in physical memory) in main memory. This counter includes both
            hard faults (those that require disk access) and soft faults (where the
            faulted page is found elsewhere in physical memory.) Most processors can
            handle large numbers of soft faults without consequence. However, hard
            faults can cause significant delays."
        ::= { cpqOsMemory 6 }

    cpqOsMemCacheFaultsPerSec OBJECT-TYPE
        SYNTAX  INTEGER
        ACCESS  read-only
        STATUS  mandatory
        DESCRIPTION
            "Cache Faults/sec is the number of faults which occur when a page sought
            in the file system cache is not found there and must be retrieved from
            elsewhere in memory (a soft fault) or from disk (a hard fault). The file
            system cache is an area of physical memory that stores recently used pages
            of data for applications. Cache activity is a reliable indicator of most
            application I/O operations. This counter counts the number of faults,
            without regard for the number of pages faulted in each operation. "
        ::= { cpqOsMemory 7 }

    cpqOsMemPageReadsPerSecx1000 OBJECT-TYPE
        SYNTAX  INTEGER
        ACCESS  read-only
        STATUS  mandatory
        DESCRIPTION
            "Page Reads/sec is the number of times the disk was read to resolve hard
             page faults (times 1000). (Hard page faults occur when a process requires
             code or data that is not in its working set or elsewhere in physical memory,
             and must be retrieved from disk). This counter was designed as a primary
             indicator of the kinds of faults that cause system-wide delays. It includes
             reads to satisfy faults in the file system cache (usually requested by
             applications) and in non-cached mapped memory files. This counter counts numbers
             of read operations, without regard to the numbers of pages retrieved by each
             operation. This counter displays the difference between the values observed
             in the last two samples, divided by the duration of the sample interval."
        ::= { cpqOsMemory 8 }

    cpqOsMemPageWritesPerSecx1000 OBJECT-TYPE
        SYNTAX  INTEGER
        ACCESS  read-only
        STATUS  mandatory
        DESCRIPTION
            "Page Writes/sec is the number of times pages were written to disk to free
             up space in physical memory (times 1000). Pages are written to disk only if
             they are changed while in physical memory, so they are likely to hold data,
             not code. This counter counts write operations, without regard to the number
             of pages written in each operation.  This counter displays the difference
             between the values observed in the last two samples, divided by the
             duration of the sample interval."
        ::= { cpqOsMemory 9 }

    cpqOsMemPoolNonpagedBytes OBJECT-TYPE
        SYNTAX  INTEGER
        ACCESS  read-only
        STATUS  mandatory
        DESCRIPTION
            "Pool Nonpaged Bytes is the number of bytes in the nonpaged pool, an area of
             system memory (physical memory used by the operating system) for objects
             that cannot be written to disk, but must remain in physical memory as long
             as they are allocated. Memory: Pool Nonpaged Bytes is calculated differently
             than Process: Pool Nonpaged Bytes, so it might not equal Process: Pool
             Nonpaged Bytes: _Total.  This counter displays the last observed value only;
             it is not an average."
        ::= { cpqOsMemory 10 }

    cpqOsMemCacheBytes OBJECT-TYPE
        SYNTAX  INTEGER
        ACCESS  read-only
        STATUS  mandatory
        DESCRIPTION
            "Cache Bytes is the sum of the System Cache Resident Bytes, System Driver
             Resident Bytes, System Code Resident Bytes, and Pool Paged Resident Bytes
             counters. This counter displays the last observed value only; it is not an
             average."
        ::= { cpqOsMemory 11 }


-- ***********************************************************************************
--   Operating System MIB Cache Group
--   ================================
--
-- The compaq enterprise               (1.3.6.1.4.1.232)
--      cpqWinOsMgmt Group             (1.3.6.1.4.1.232.19)
--       cpqOsComponent Group          (1.3.6.1.4.1.232.19.2)
--        cpqOsCache Group             (1.3.6.1.4.1.232.19.2.5)
--         cpqOsCacheTable             (1.3.6.1.4.1.232.19.2.5.2)
--
--  The cpqOsCache group describes the System Cache Performance properties.
--
-- ***********************************************************************************

    cpqOsCacheStatus OBJECT-TYPE
        SYNTAX  INTEGER {
            other(1),
            ok(2),
            degraded(3),
            failed(4)
            }
        ACCESS  read-only
        STATUS  mandatory
        DESCRIPTION
            "This value specifies the overall condition of Cache Object."
        ::= { cpqOsCache 1 }

    cpqOsCacheTable OBJECT-TYPE
        SYNTAX  SEQUENCE OF CpqOsCacheEntry
        ACCESS  not-accessible
        STATUS  mandatory
        DESCRIPTION
            "A table of Cache Entries."
        ::= { cpqOsCache 2 }

    cpqOsCacheEntry OBJECT-TYPE
        SYNTAX  CpqOsCacheEntry
        ACCESS  not-accessible
        STATUS  mandatory
        DESCRIPTION
            "A Cache Entry."
        INDEX   { cpqOsCacheIndex }
        ::= { cpqOsCacheTable 1 }

        CpqOsCacheEntry ::= SEQUENCE {
            cpqOsCacheIndex                  INTEGER,
            cpqOsCacheInstance               DisplayString,
            cpqOsCacheCopyReadHitsPercent    INTEGER,
            cpqOsWarCacheCopyReadHitsPercent INTEGER,
            cpqOsCriCacheCopyReadHitsPercent INTEGER,
            cpqOsCacheCopyReadsPerSec        INTEGER,
            cpqOsCacheCondition              INTEGER
        }

    cpqOsCacheIndex OBJECT-TYPE
        SYNTAX  INTEGER
        ACCESS  read-only
        STATUS  mandatory
        DESCRIPTION
            "The Cache Instance number."
        ::= { cpqOsCacheEntry 1 }

    cpqOsCacheInstance OBJECT-TYPE
        SYNTAX  DisplayString (SIZE (0..64))
        ACCESS  read-only
        STATUS  mandatory
        DESCRIPTION
            "The Cache Instance Name."
        ::= { cpqOsCacheEntry 2 }

    cpqOsCacheCopyReadHitsPercent OBJECT-TYPE
        SYNTAX  INTEGER
        ACCESS  read-only
        STATUS  mandatory
        DESCRIPTION
            "%Copy Read Hits is the percentage of cache copy read requests that hit
            the cache, that is, they did not require a disk read in order to provide
            access to the page in the cache. A copy read is a file read operation that
            is satisfied by a memory copy from a page in the cache to the application
            buffer. The LAN Redirector uses this method for retrieving information
            from the cache, as does the LAN Server for small transfers. This is a
            method used by the disk file systems as well."
        ::= { cpqOsCacheEntry 3 }

    cpqOsWarCacheCopyReadHitsPercent OBJECT-TYPE
        SYNTAX  INTEGER
        ACCESS  read-write
        STATUS  mandatory
        DESCRIPTION
            "Warning alarm will be issued if,
              (cpqOsCacheCopyReadHitsPercent <= cpqOsWarCacheCopyReadHitsPercent &&
               cpqOsCacheCopyReadHitsPercent > cpqOsCriCacheCopyReadsPerSec)
            for 15 data collection intervals."
        ::= { cpqOsCacheEntry 4 }

    cpqOsCriCacheCopyReadHitsPercent OBJECT-TYPE
        SYNTAX  INTEGER
        ACCESS  read-write
        STATUS  mandatory
        DESCRIPTION
            "Critical alarm will be issued if,
               (cpqOsCacheCopyReadHitsPercent <= cpqOsCriCacheCopyReadHitsPercent)
             for 15 data collection intervals."
        ::= { cpqOsCacheEntry 5 }

    cpqOsCacheCopyReadsPerSec OBJECT-TYPE
        SYNTAX  INTEGER
        ACCESS  read-only
        STATUS  mandatory
        DESCRIPTION
            "Copy Reads/sec is the frequency of reads from pages of the file system
            cache that involve a memory copy of the data from the cache to the
            application's buffer. The LAN Redirector uses this method for
            retrieving information from the file system cache, as does the LAN Server
            for small transfers."
        ::= { cpqOsCacheEntry 6 }

    cpqOsCacheCondition OBJECT-TYPE
        SYNTAX  INTEGER {
            other(1),
            ok(2),
            degraded(3),
            failed(4)
            }
        ACCESS  read-only
        STATUS  mandatory
        DESCRIPTION
            "The condition of this Cache Object Instance."
        ::= { cpqOsCacheEntry 7 }

-- ***********************************************************************************
--   Operating System MIB Paging File Group
--   ======================================
--
-- The compaq enterprise               (1.3.6.1.4.1.232)
--      cpqWinOsMgmt Group             (1.3.6.1.4.1.232.19)
--       cpqOsComponent Group          (1.3.6.1.4.1.232.19.2)
--        cpqOsPagingFile Group        (1.3.6.1.4.1.232.19.2.6)
--         cpqOsPagingFileTable        (1.3.6.1.4.1.232.19.2.6.2)
--
--  The cpqOsPagingFile group describes the System Paging File Performance properties.
--
-- ***********************************************************************************

    cpqOsPagingFileStatus OBJECT-TYPE
        SYNTAX  INTEGER {
            other(1),
            ok(2),
            degraded(3),
            failed(4)
            }
        ACCESS  read-only
        STATUS  mandatory
        DESCRIPTION
            "This value specifies the overall condition of Paging File Object
            instances."
        ::= { cpqOsPagingFile 1 }

    cpqOsPagingFileTable OBJECT-TYPE
        SYNTAX  SEQUENCE OF CpqOsPagingFileEntry
        ACCESS  not-accessible
        STATUS  mandatory
        DESCRIPTION
            "A table of Paging File Entries."
        ::= { cpqOsPagingFile 2 }

    cpqOsPagingFileEntry OBJECT-TYPE
        SYNTAX  CpqOsPagingFileEntry
        ACCESS  not-accessible
        STATUS  mandatory
        DESCRIPTION
            "A Paging File Entry."
        INDEX   { cpqOsPagingFileIndex }
        ::= { cpqOsPagingFileTable 1 }

        CpqOsPagingFileEntry ::= SEQUENCE {
            cpqOsPagingFileIndex         INTEGER,
            cpqOsPagingFileInstance      DisplayString,
            cpqOsPageFileUsagePercent    INTEGER,
            cpqOsWarPageFileUsagePercent INTEGER,
            cpqOsCriPageFileUsagePercent INTEGER,
            cpqOsPagingFileCondition     INTEGER
        }

    cpqOsPagingFileIndex OBJECT-TYPE
        SYNTAX  INTEGER
        ACCESS  read-only
        STATUS  mandatory
        DESCRIPTION
            "This PagingFile Instance Number."
        ::= { cpqOsPagingFileEntry 1 }

    cpqOsPagingFileInstance OBJECT-TYPE
        SYNTAX  DisplayString (SIZE (0..64))
        ACCESS  read-only
        STATUS  mandatory
        DESCRIPTION
            "This PagingFile Instance Name."
        ::= { cpqOsPagingFileEntry 2 }

    cpqOsPageFileUsagePercent OBJECT-TYPE
        SYNTAX  INTEGER
        ACCESS  read-only
        STATUS  mandatory
        DESCRIPTION
            "The Paging File usage in percent."
        ::= { cpqOsPagingFileEntry 3 }

    cpqOsWarPageFileUsagePercent OBJECT-TYPE
        SYNTAX  INTEGER
        ACCESS  read-write
        STATUS  mandatory
        DESCRIPTION
            "Warning alarm will be issued if,
              (cpqOsPageFileUsagePercent >= cpqOsWarPageFileUsagePercent  &&
               cpqOsPageFileUsagePercent < cpqOsCriPageFileUsagePercent)
            for 15 data collection intervals."
        ::= { cpqOsPagingFileEntry 4 }

    cpqOsCriPageFileUsagePercent OBJECT-TYPE
        SYNTAX  INTEGER
        ACCESS  read-write
        STATUS  mandatory
        DESCRIPTION
            "Critical alarm will be issued if,
              (cpqOsPageFileUsagePercent >= cpqOsCriPageFileUsagePercent)
            for 15 data collection intervals."
        ::= { cpqOsPagingFileEntry 5 }

    cpqOsPagingFileCondition OBJECT-TYPE
        SYNTAX  INTEGER {
            other(1),
            ok(2),
            degraded(3),
            failed(4)
            }
        ACCESS  read-only
        STATUS  mandatory
        DESCRIPTION
            "The condition of this Paging File Object Instance."
        ::= { cpqOsPagingFileEntry 6 }

    cpqOsPagingFileOSManaged OBJECT-TYPE
        SYNTAX  INTEGER    
        ACCESS  read-only
        STATUS  mandatory
        DESCRIPTION
           "Boolean values of 0 or 1. 1 means the pagefile is managed by
            the operating system. This value should be the same value as
            AutomaticManagedPagefile property of Windows WMI
            root\cimv2 Win32_ComputerSystem class."
        ::= { cpqOsPagingFile 3 }


-- ***********************************************************************************
--   Operating System MIB Physical Disk Group
--   ========================================
--
-- The compaq enterprise               (1.3.6.1.4.1.232)
--      cpqWinOsMgmt Group             (1.3.6.1.4.1.232.19)
--       cpqOsComponent Group          (1.3.6.1.4.1.232.19.2)
--        cpqOsPhysicalDisk Group      (1.3.6.1.4.1.232.19.2.7)
--         cpqOsPhysicalDiskTable      (1.3.6.1.4.1.232.19.2.7.2)
--
--  The cpqOsPhysicalDisk group describes the Physical Disk Performance properties.
--
-- ***********************************************************************************

    cpqOsPhysicalDiskStatus OBJECT-TYPE
        SYNTAX  INTEGER {
            other(1),
            ok(2),
            degraded(3),
            failed(4)
            }
        ACCESS  read-only
        STATUS  mandatory
        DESCRIPTION
            "This value specifies the overall condition of Physical Disk Object
            instances."
        ::= { cpqOsPhysicalDisk 1 }

    cpqOsPhysicalDiskTable OBJECT-TYPE
        SYNTAX  SEQUENCE OF CpqOsPhysicalDiskEntry
        ACCESS  not-accessible
        STATUS  mandatory
        DESCRIPTION
            "A table of Physical Disk Entries."
        ::= { cpqOsPhysicalDisk 2 }

    cpqOsPhysicalDiskEntry OBJECT-TYPE
        SYNTAX  CpqOsPhysicalDiskEntry
        ACCESS  not-accessible
        STATUS  mandatory
        DESCRIPTION
            "A Physical Disk Entry."
        INDEX   { cpqOsPhysicalDiskIndex }
        ::= { cpqOsPhysicalDiskTable 1 }

        CpqOsPhysicalDiskEntry ::= SEQUENCE {
            cpqOsPhysicalDiskIndex                       INTEGER,
            cpqOsPhysicalDiskInstance                    DisplayString,
            cpqOsPhysicalDiskQueueLength                 INTEGER,
            cpqOsPhysicalDiskBusyTimePercent             INTEGER,
            cpqOsPhysicalDiskCondition                   INTEGER,
            cpqOsPhysicalDiskBytesPersec                 INTEGER,
            cpqOsPhysicalDiskTransfersPersecx1000        INTEGER,
            cpqOsPhysicalDiskReadsPersecx1000            INTEGER,
            cpqOsPhysicalDiskWritesPersecx1000           INTEGER,
            cpqOsPhysicalDiskReadBytesPersec             INTEGER,
            cpqOsPhysicalDiskWriteBytesPersec            INTEGER,
            cpqOsPhysicalDiskAvgDisksecPerReadx10000     INTEGER,
            cpqOsPhysicalDiskAvgDisksecPerWritex10000    INTEGER,
            cpqOsPhysicalDiskCurrentDiskQueueLength      INTEGER
        }

    cpqOsPhysicalDiskIndex OBJECT-TYPE
        SYNTAX  INTEGER
        ACCESS  read-only
        STATUS  mandatory
        DESCRIPTION
            "The Physical Disk Instance number."
        ::= { cpqOsPhysicalDiskEntry 1 }

    cpqOsPhysicalDiskInstance OBJECT-TYPE
        SYNTAX  DisplayString (SIZE (0..64))
        ACCESS  read-only
        STATUS  mandatory
        DESCRIPTION
            "The Physical Disk Instance Name."
        ::= { cpqOsPhysicalDiskEntry 2 }

    cpqOsPhysicalDiskQueueLength OBJECT-TYPE
        SYNTAX  INTEGER
        ACCESS  read-only
        STATUS  mandatory
        DESCRIPTION
            "Avg. Disk Queue Length is the average number of both read and write
            requests that were queued for the selected disk during the sample
            interval."
        ::= { cpqOsPhysicalDiskEntry 3 }

    cpqOsPhysicalDiskBusyTimePercent OBJECT-TYPE
        SYNTAX  INTEGER
        ACCESS  read-only
        STATUS  mandatory
        DESCRIPTION
            "%Disk Time is the percentage of elapsed time that the selected disk
            drive is busy servicing read or write requests."
        ::= { cpqOsPhysicalDiskEntry 4 }

    cpqOsPhysicalDiskCondition OBJECT-TYPE
        SYNTAX  INTEGER {
            other(1),
            ok(2),
            degraded(3),
            failed(4)
            }
        ACCESS  read-only
        STATUS  mandatory
        DESCRIPTION
            "The condition of this Physical Disk Object Instance."
        ::= { cpqOsPhysicalDiskEntry 5 }

    cpqOsPhysicalDiskBytesPersec OBJECT-TYPE
        SYNTAX  INTEGER
        ACCESS  read-only
        STATUS  mandatory
        DESCRIPTION
            "Disk Bytes/sec is the rate bytes are transferred to or from the disk during
             write or read operations."
        ::= { cpqOsPhysicalDiskEntry 6 }

     cpqOsPhysicalDiskTransfersPersecx1000 OBJECT-TYPE
        SYNTAX  INTEGER
        ACCESS  read-only
        STATUS  mandatory
        DESCRIPTION
            "Disk Transfers/sec is the rate of read and write operations on the disk (times 1000)."
        ::= { cpqOsPhysicalDiskEntry 7 }

     cpqOsPhysicalDiskReadsPersecx1000 OBJECT-TYPE
        SYNTAX  INTEGER
        ACCESS  read-only
        STATUS  mandatory
        DESCRIPTION
            "Disk Reads/sec is the rate of read operations on the disk (times 1000)."
        ::= { cpqOsPhysicalDiskEntry 8 }

     cpqOsPhysicalDiskWritesPersecx1000 OBJECT-TYPE
        SYNTAX  INTEGER
        ACCESS  read-only
        STATUS  mandatory
        DESCRIPTION
            "Disk Writes/sec is the rate of write operations on the disk (times 1000)."
        ::= { cpqOsPhysicalDiskEntry 9 }

     cpqOsPhysicalDiskReadBytesPersec OBJECT-TYPE
        SYNTAX  INTEGER
        ACCESS  read-only
        STATUS  mandatory
        DESCRIPTION
            "Disk Read Bytes/sec is the rate bytes are transferred from the disk during
             read operations."
        ::= { cpqOsPhysicalDiskEntry 10 }

     cpqOsPhysicalDiskWriteBytesPersec OBJECT-TYPE
        SYNTAX  INTEGER
        ACCESS  read-only
        STATUS  mandatory
        DESCRIPTION
            "Disk Write Bytes is rate bytes are transferred to the disk during write
             operations."
        ::= { cpqOsPhysicalDiskEntry 11 }

     cpqOsPhysicalDiskAvgDisksecPerReadx10000 OBJECT-TYPE
        SYNTAX  INTEGER
        ACCESS  read-only
        STATUS  mandatory
        DESCRIPTION
            "Avg. Disk sec/Read is the average time in seconds of a read of data from the
             disk (times 10000)."
        ::= { cpqOsPhysicalDiskEntry 12 }

     cpqOsPhysicalDiskAvgDisksecPerWritex10000 OBJECT-TYPE
        SYNTAX  INTEGER
        ACCESS  read-only
        STATUS  mandatory
        DESCRIPTION
            "Avg. Disk sec/Write is the average time in seconds of a write of data to the
             disk (times 10000)."
        ::= { cpqOsPhysicalDiskEntry 13 }

     cpqOsPhysicalDiskCurrentDiskQueueLength OBJECT-TYPE
        SYNTAX  INTEGER
        ACCESS  read-only
        STATUS  mandatory
        DESCRIPTION
            "Current Disk Queue Length is the number of requests outstanding
            on the disk at the time the performance data is collected. It includes requests
            in service at the time of the snapshot. This is an instantaneous length, not an
            average over the time interval. Multi-spindle disk devices can have multiple
            requests active at one time, but other concurrent requests are awaiting
            service. This counter might reflect a transitory high or low queue length, but
            if there is a sustained load on the disk drive, it is likely that this will be
            consistently high.  Requests are experiencing delays proportional to the
            length of this queue minus the number of spindles on the disks.  This
            difference should average less than 2 for good performance."
        ::= { cpqOsPhysicalDiskEntry 14 }

-- ***********************************************************************************
--   Operating System MIB Logical Disk Group
--   =======================================
--
-- The compaq enterprise               (1.3.6.1.4.1.232)
--      cpqWinOsMgmt Group             (1.3.6.1.4.1.232.19)
--       cpqOsComponent Group          (1.3.6.1.4.1.232.19.2)
--        cpqOsLogicalDisk Group       (1.3.6.1.4.1.232.19.2.8)
--         cpqOsLogicalDiskTable       (1.3.6.1.4.1.232.19.2.8.2)
--
--  The cpqOsLogicalDisk group describes the Logical Disk Performance properties.
--
-- ***********************************************************************************

    cpqOsLogicalDiskStatus OBJECT-TYPE
        SYNTAX  INTEGER {
            other(1),
            ok(2),
            degraded(3),
            failed(4)
            }
        ACCESS  read-only
        STATUS  mandatory
        DESCRIPTION
            "This value specifies the overall condition of Logical Disk Object
            instances."
        ::= { cpqOsLogicalDisk 1 }

    cpqOsLogicalDiskTable OBJECT-TYPE
        SYNTAX  SEQUENCE OF CpqOsLogicalDiskEntry
        ACCESS  not-accessible
        STATUS  mandatory
        DESCRIPTION
            "A table of Logical Disk Entries."
        ::= { cpqOsLogicalDisk 2 }

    cpqOsLogicalDiskEntry OBJECT-TYPE
        SYNTAX  CpqOsLogicalDiskEntry
        ACCESS  not-accessible
        STATUS  mandatory
        DESCRIPTION
            "A Logical Disk Entry."
        INDEX   { cpqOsLogicalDiskIndex }
        ::= { cpqOsLogicalDiskTable 1 }

        CpqOsLogicalDiskEntry ::= SEQUENCE {
            cpqOsLogicalDiskIndex               INTEGER,
            cpqOsLogicalDiskInstance            DisplayString,
            cpqOsLogicalDiskFreeSpaceMBytes     INTEGER,
            cpqOsLogicalDiskFreeSpacePercent    INTEGER,
            cpqOsLogicalDiskQueueLength         INTEGER,
            cpqOsLogicalDiskBusyTimePercent     INTEGER,
            cpqOsWarLogicalDiskBusyTimePercent  INTEGER,
            cpqOsCriLogicalDiskBusyTimePercent  INTEGER,
            cpqOsLogicalDiskCondition           INTEGER
        }

    cpqOsLogicalDiskIndex OBJECT-TYPE
        SYNTAX  INTEGER
        ACCESS  read-only
        STATUS  mandatory
        DESCRIPTION
            "The Logical Disk Instance number."
        ::= { cpqOsLogicalDiskEntry 1 }

    cpqOsLogicalDiskInstance OBJECT-TYPE
        SYNTAX  DisplayString (SIZE (0..64))
        ACCESS  read-only
        STATUS  mandatory
        DESCRIPTION
            "The Logical Disk Instance Name."
        ::= { cpqOsLogicalDiskEntry 2 }

    cpqOsLogicalDiskFreeSpaceMBytes OBJECT-TYPE
        SYNTAX  INTEGER
        ACCESS  read-only
        STATUS  mandatory
        DESCRIPTION
            "Free Megabytes displays the unallocated space on the disk drive
            in megabytes. One megabyte = 1,048,576 bytes."
        ::= { cpqOsLogicalDiskEntry 3 }

    cpqOsLogicalDiskFreeSpacePercent OBJECT-TYPE
        SYNTAX  INTEGER
        ACCESS  read-only
        STATUS  mandatory
        DESCRIPTION
            "%Free Space is the ratio of the free space available on the
            logical disk unit to the total usable space provided by the selected
            logical disk drive"
        ::= { cpqOsLogicalDiskEntry 4 }

    cpqOsLogicalDiskQueueLength OBJECT-TYPE
        SYNTAX  INTEGER
        ACCESS  read-only
        STATUS  mandatory
        DESCRIPTION
            "Avg. Disk Queue Length is the average number of both read and write
            requests that were queued for the selected disk during the sample
            interval."
        ::= { cpqOsLogicalDiskEntry 5 }

    cpqOsLogicalDiskBusyTimePercent OBJECT-TYPE
        SYNTAX  INTEGER
        ACCESS  read-only
        STATUS  mandatory
        DESCRIPTION
            "%Disk Time is the percentage of elapsed time that the selected disk
            drive is busy servicing read or write requests."
        ::= { cpqOsLogicalDiskEntry 6 }

    cpqOsWarLogicalDiskBusyTimePercent OBJECT-TYPE
        SYNTAX  INTEGER
        ACCESS  read-write
        STATUS  mandatory
        DESCRIPTION
            "Warning alarm will be issued if,
            (cpqOsLogicalDiskBusyTimePercent >= cpqOsWarLogicalDiskBusyTimePercent  &&
             cpqOsLogicalDiskBusyTimePercent < cpqOsCriLogicalDiskBusyTimePercent)
            for 15 data collection intervals."
        ::= { cpqOsLogicalDiskEntry 7 }

    cpqOsCriLogicalDiskBusyTimePercent OBJECT-TYPE
        SYNTAX  INTEGER
        ACCESS  read-write
        STATUS  mandatory
        DESCRIPTION
            "Critical alarm will be issued if,
              (cpqOsLogicalDiskBusyTimePercent >= cpqOsCriLogicalDiskBusyTimePercent)
            for 15 data collection intervals."
        ::= { cpqOsLogicalDiskEntry 8 }

    cpqOsLogicalDiskCondition OBJECT-TYPE
        SYNTAX  INTEGER {
            other(1),
            ok(2),
            degraded(3),
            failed(4)
            }
        ACCESS  read-only
        STATUS  mandatory
        DESCRIPTION
            "The condition of this Logical Disk Object Instance."
        ::= { cpqOsLogicalDiskEntry 9 }

-- ***********************************************************************************
--   Operating System MIB Server Group
--   =================================
--
-- The compaq enterprise               (1.3.6.1.4.1.232)
--      cpqWinOsMgmt Group             (1.3.6.1.4.1.232.19)
--       cpqOsComponent Group          (1.3.6.1.4.1.232.19.2)
--        cpqOsServer Group            (1.3.6.1.4.1.232.19.2.9)
--
--  The cpqOsServer group describes the Server Performance properties.
--
-- ***********************************************************************************

    cpqOsServerStatus OBJECT-TYPE
        SYNTAX  INTEGER {
            other(1),
            ok(2),
            degraded(3),
            failed(4)
            }
        ACCESS  read-only
        STATUS  mandatory
        DESCRIPTION
            "This value specifies the overall condition of Server Object."
        ::= { cpqOsServer 1 }

    cpqOsServerTotalNetworkUtilizationBytesPerSec OBJECT-TYPE
        SYNTAX  INTEGER
        ACCESS  read-only
        STATUS  mandatory
        DESCRIPTION
            "The number of bytes the server has sent to and received from the
            network. This value provides an overall indication of how busy the
            server is."
        ::= { cpqOsServer 2 }

    cpqOsServerSessions OBJECT-TYPE
        SYNTAX  INTEGER
        ACCESS  read-only
        STATUS  mandatory
        DESCRIPTION
            "The number of sessions currently active in the server. Indicates
            current server activity."
        ::= { cpqOsServer 3 }

    cpqOsServerAccessPermissionErrors OBJECT-TYPE
        SYNTAX  INTEGER
        ACCESS  read-only
        STATUS  mandatory
        DESCRIPTION
            "The number of times opens on behalf of clients have failed
            with STATUS_ACCESS_DENIED. Can indicate whether somebody is
            randomly attempting to access files in hopes of getting at
            something that was not properly protected."
        ::= { cpqOsServer 4 }

    cpqOsServerAccessGrantedErrors OBJECT-TYPE
        SYNTAX  INTEGER
        ACCESS  read-only
        STATUS  mandatory
        DESCRIPTION
            "The number of times accesses to files opened successfully were
            denied. Can indicate attempts to access files without proper
            access authorization."
        ::= { cpqOsServer 5 }

    cpqOsServerLogonErrors OBJECT-TYPE
        SYNTAX  INTEGER
        ACCESS  read-only
        STATUS  mandatory
        DESCRIPTION
            "The number of failed logon attempts to the server. Can indicate
            whether password guessing programs are being used to crack the
            security on the server."
        ::= { cpqOsServer 6 }

    cpqOsServerSessionsErroredOut OBJECT-TYPE
        SYNTAX  INTEGER
        ACCESS  read-only
        STATUS  mandatory
        DESCRIPTION
            "The number of sessions that have been closed due to unexpected error
            conditions or sessions that have reached the autodisconnect timeout
            and have been disconnected normally."
        ::= { cpqOsServer 7 }

    cpqOsServerContextBlocksQueuePerSec OBJECT-TYPE
        SYNTAX  INTEGER
        ACCESS  read-only
        STATUS  mandatory
        DESCRIPTION
            "Context Blocks Queued per second is the rate at which work context
            blocks had to be placed on the server's FSP queue to await server action."
        ::= { cpqOsServer 8 }

-- ***********************************************************************************
--   Operating System MIB Network Interface Group
--   ============================================
--
-- The compaq enterprise               (1.3.6.1.4.1.232)
--      cpqWinOsMgmt Group             (1.3.6.1.4.1.232.19)
--       cpqOsComponent Group          (1.3.6.1.4.1.232.19.2)
--        cpqOsNetworkInterface Group  (1.3.6.1.4.1.232.19.2.10)
--         cpqOsNetworkInterfaceTable  (1.3.6.1.4.1.232.19.2.10.2)
--
--  The cpqOsNetworkInterface group describes the Network Performance properties.
--
-- ***********************************************************************************

    cpqOsNetworkInterfaceStatus OBJECT-TYPE
        SYNTAX  INTEGER {
            other(1),
            ok(2),
            degraded(3),
            failed(4)
            }
        ACCESS  read-only
        STATUS  mandatory
        DESCRIPTION
            "This value specifies the overall condition of Network Interface Object
            instances."
        ::= { cpqOsNetworkInterface 1 }

    cpqOsNetworkInterfaceTable OBJECT-TYPE
        SYNTAX  SEQUENCE OF CpqOsNetworkInterfaceEntry
        ACCESS  not-accessible
        STATUS  mandatory
        DESCRIPTION
            "A table of Network Interface Entries."
        ::= { cpqOsNetworkInterface 2 }

    cpqOsNetworkInterfaceEntry OBJECT-TYPE
        SYNTAX  CpqOsNetworkInterfaceEntry
        ACCESS  not-accessible
        STATUS  mandatory
        DESCRIPTION
            "A Network Interface Entry."
        INDEX   { cpqOsNetworkInterfaceIndex }
        ::= { cpqOsNetworkInterfaceTable 1 }

        CpqOsNetworkInterfaceEntry ::= SEQUENCE {
            cpqOsNetworkInterfaceIndex             INTEGER,
            cpqOsNetworkInterfaceInstance          DisplayString,
            cpqOsNetworkTotalBytesPerSec           INTEGER,
            cpqOsNetworkPacketsPerSec              INTEGER,
            cpqOsNetworkOutputQueueLength          INTEGER,
            cpqOsNetworkPktOutboundErrors          INTEGER,
            cpqOsNetworkPktReceiveErrors           INTEGER,
            cpqOsNetworkCurrentBandWidth           INTEGER,
            cpqOsNetworkInterfaceCondition         INTEGER,
            cpqOsNetworkBytesSentPersec            INTEGER,
            cpqOsNetworkBytesReceivedPersec        INTEGER,
            cpqOsNetworkPacketsSentPersecx1000     INTEGER,
            cpqOsNetworkPacketsReceivedPersecx1000 INTEGER
        }

    cpqOsNetworkInterfaceIndex OBJECT-TYPE
        SYNTAX  INTEGER
        ACCESS  read-only
        STATUS  mandatory
        DESCRIPTION
            "The Network Interface Instance number."
        ::= { cpqOsNetworkInterfaceEntry 1 }

    cpqOsNetworkInterfaceInstance OBJECT-TYPE
        SYNTAX  DisplayString (SIZE (0..64))
        ACCESS  read-only
        STATUS  mandatory
        DESCRIPTION
            "The Network Interface Instance Name."
        ::= { cpqOsNetworkInterfaceEntry 2 }

    cpqOsNetworkTotalBytesPerSec OBJECT-TYPE
        SYNTAX  INTEGER
        ACCESS  read-only
        STATUS  mandatory
        DESCRIPTION
            "Bytes Total/sec is the rate at which bytes are sent and received
            on the interface, including framing characters."
        ::= { cpqOsNetworkInterfaceEntry 3 }

    cpqOsNetworkPacketsPerSec OBJECT-TYPE
        SYNTAX  INTEGER
        ACCESS  read-only
        STATUS  mandatory
        DESCRIPTION
            "Packets/sec is the rate at which packets are sent and received
            on the network interface."
        ::= { cpqOsNetworkInterfaceEntry 4 }

    cpqOsNetworkOutputQueueLength OBJECT-TYPE
        SYNTAX  INTEGER
        ACCESS  read-only
        STATUS  mandatory
        DESCRIPTION
            "Output Queue Length is the length of the output packet queue
            (in packets.) If this is longer than 2, delays are being
            experienced and the bottleneck should be found and eliminated
            if possible. Since the requests are queued by NDIS in this
            implementations, this will always be 0."
        ::= { cpqOsNetworkInterfaceEntry 5 }

    cpqOsNetworkPktOutboundErrors OBJECT-TYPE
        SYNTAX  INTEGER
        ACCESS  read-only
        STATUS  mandatory
        DESCRIPTION
            "Packets Outbound Errors is the number of outbound packets that
            could not be transmitted because of errors."
        ::= { cpqOsNetworkInterfaceEntry 6 }

    cpqOsNetworkPktReceiveErrors OBJECT-TYPE
        SYNTAX  INTEGER
        ACCESS  read-only
        STATUS  mandatory
        DESCRIPTION
            "Packets Received Errors is the number of inbound packets that
            contained errors preventing them from being deliverable to a
            higher-layer protocol."
        ::= { cpqOsNetworkInterfaceEntry 7 }

    cpqOsNetworkCurrentBandWidth OBJECT-TYPE
        SYNTAX  INTEGER
        ACCESS  read-only
        STATUS  mandatory
        DESCRIPTION
            "Current Bandwidth is an estimate of the interface's current
            bandwidth in bits per second (BPS).  For interfaces that do not
            vary in bandwidth or for those where no accurate estimation can
            be made, this value is the nominal bandwidth."
        ::= { cpqOsNetworkInterfaceEntry 8 }

    cpqOsNetworkInterfaceCondition OBJECT-TYPE
        SYNTAX  INTEGER {
            other(1),
            ok(2),
            degraded(3),
            failed(4)
            }
        ACCESS  read-only
        STATUS  mandatory
        DESCRIPTION
            "The condition of this Network Interface Object Instance."
        ::= { cpqOsNetworkInterfaceEntry 9 }

    cpqOsNetworkBytesSentPersec OBJECT-TYPE
        SYNTAX  INTEGER
        ACCESS  read-only
        STATUS  mandatory
        DESCRIPTION
            "Bytes Sent/sec is the rate at which bytes are sent on the interface,
            including framing characters."
        ::= { cpqOsNetworkInterfaceEntry 10 }

    cpqOsNetworkBytesReceivedPersec OBJECT-TYPE
        SYNTAX  INTEGER
        ACCESS  read-only
        STATUS  mandatory
        DESCRIPTION
            "Bytes Received/sec is the rate at which bytes are received on the
            interface, including framing characters."
        ::= { cpqOsNetworkInterfaceEntry 11 }

    cpqOsNetworkPacketsSentPersecx1000 OBJECT-TYPE
        SYNTAX  INTEGER
        ACCESS  read-only
        STATUS  mandatory
        DESCRIPTION
            "Packets Sent/sec is the rate (times 1000) at which packets are sent on
            the network interface."
        ::= { cpqOsNetworkInterfaceEntry 12 }

    cpqOsNetworkPacketsReceivedPersecx1000 OBJECT-TYPE
        SYNTAX  INTEGER
        ACCESS  read-only
        STATUS  mandatory
        DESCRIPTION
            "Packets Received/sec is the rate (times 1000) at which packets are received
            on the network interface."
        ::= { cpqOsNetworkInterfaceEntry 13 }

-- ***********************************************************************************
--   Operating System MIB Tcp protocol Group
--   =======================================
--
-- The compaq enterprise               (1.3.6.1.4.1.232)
--      cpqWinOsMgmt Group             (1.3.6.1.4.1.232.19)
--       cpqOsComponent Group          (1.3.6.1.4.1.232.19.2)
--        cpqOsTcp Group               (1.3.6.1.4.1.232.19.2.11)
--         cpqOsTcpTable               (1.3.6.1.4.1.232.19.2.11.2)
--
--  The cpqOsTcp group describes the Tcp protocol Performance properties.
--
-- ***********************************************************************************

    cpqOsTcpStatus OBJECT-TYPE
        SYNTAX  INTEGER {
            other(1),
            ok(2),
            degraded(3),
            failed(4)
            }
        ACCESS  read-only
        STATUS  mandatory
        DESCRIPTION
            "This value specifies the overall condition of TCP Object instances."
        ::= { cpqOsTcp 1 }

    cpqOsTcpTable OBJECT-TYPE
        SYNTAX  SEQUENCE OF CpqOsTcpEntry
        ACCESS  not-accessible
        STATUS  mandatory
        DESCRIPTION
            "A table of Tcp Entries."
        ::= { cpqOsTcp 2 }

    cpqOsTcpEntry OBJECT-TYPE
        SYNTAX  CpqOsTcpEntry
        ACCESS  not-accessible
        STATUS  mandatory
        DESCRIPTION
            "A TCP Entry."
        INDEX   { cpqOsTcpIndex }
        ::= { cpqOsTcpTable 1 }

        CpqOsTcpEntry ::= SEQUENCE {
            cpqOsTcpIndex                         INTEGER,
            cpqOsTcpInstance                      DisplayString,
            cpqOsTcpActiveConnections             INTEGER,
            cpqOsTcpEstablishedConections         INTEGER,
            cpqOsTcpSegmentsPerSec                INTEGER,
            cpqOsTcpRetransmittedSegmentsPerSec   INTEGER,
            cpqOsTcpConnectionFailures            INTEGER,
            cpqOsTcpCondition                     INTEGER
        }

    cpqOsTcpIndex OBJECT-TYPE
        SYNTAX  INTEGER
        ACCESS  read-only
        STATUS  mandatory
        DESCRIPTION
            "The TCP Instance number."
        ::= { cpqOsTcpEntry 1 }

    cpqOsTcpInstance OBJECT-TYPE
        SYNTAX  DisplayString (SIZE (0..64))
        ACCESS  read-only
        STATUS  mandatory
        DESCRIPTION
            "The TCP Instance Name."
        ::= { cpqOsTcpEntry 2 }

    cpqOsTcpActiveConnections OBJECT-TYPE
        SYNTAX  INTEGER
        ACCESS  read-only
        STATUS  mandatory
        DESCRIPTION
            "Connections Active is the number of times TCP connections have
            made a direct transition to the SYN-SENT state from the CLOSED state."
        ::= { cpqOsTcpEntry 3 }

    cpqOsTcpEstablishedConections OBJECT-TYPE
        SYNTAX  INTEGER
        ACCESS  read-only
        STATUS  mandatory
        DESCRIPTION
            "Connections Established is the number of TCP connections for
            which the current state is either ESTABLISHED or CLOSE-WAIT."
        ::= { cpqOsTcpEntry 4 }

    cpqOsTcpSegmentsPerSec OBJECT-TYPE
        SYNTAX  INTEGER
        ACCESS  read-only
        STATUS  mandatory
        DESCRIPTION
            "Segments/sec is the rate at which TCP segments are sent or
            received using the TCP protocol."
        ::= { cpqOsTcpEntry 5 }

    cpqOsTcpRetransmittedSegmentsPerSec OBJECT-TYPE
        SYNTAX  INTEGER
        ACCESS  read-only
        STATUS  mandatory
        DESCRIPTION
            "Segments Retransmitted/sec is the rate at which segments are
            retransmitted, that is, segments transmitted containing one or
            more previously transmitted bytes."
        ::= { cpqOsTcpEntry 6 }

    cpqOsTcpConnectionFailures OBJECT-TYPE
        SYNTAX  INTEGER
        ACCESS  read-only
        STATUS  mandatory
        DESCRIPTION
            "Connection Failures is the number of times TCP connections have made a
            direct transition to the CLOSED state from the SYN-SENT state or the
            SYN-RCVD state, plus the number of times TCP connections have made a
            direct transition to the LISTEN state from the SYN-RCVD state."
        ::= { cpqOsTcpEntry 7 }

    cpqOsTcpCondition OBJECT-TYPE
        SYNTAX  INTEGER {
            other(1),
            ok(2),
            degraded(3),
            failed(4)
            }
        ACCESS  read-only
        STATUS  mandatory
        DESCRIPTION
            "The condition of this Tcp Object Instance."
        ::= { cpqOsTcpEntry 8 }

-- ***********************************************************************************
--   Operating System MIB Processes Group
--   ====================================
--
-- The compaq enterprise         (1.3.6.1.4.1.232)
--      cpqWinOsMgmt Group       (1.3.6.1.4.1.232.19)
--       cpqOsComponent Group    (1.3.6.1.4.1.232.19.2)
--         cpqOsProcess Group    (1.3.6.1.4.1.232.19.2.12)
--           cpqOsProcessTable   (1.3.6.1.4.1.232.19.2.12.2)
--
--  The cpqOsProcess group describes the Processes performance properties.
--
-- ***********************************************************************************

    cpqOsProcessStatus OBJECT-TYPE
        SYNTAX  INTEGER {
            other(1),
            ok(2),
            degraded(3),
            failed(4)
            }
        ACCESS  read-only
        STATUS  mandatory
        DESCRIPTION
            "This value specifies the overall condition of Process Object instances."
        ::= { cpqOsProcess 1 }

    cpqOsProcessTable OBJECT-TYPE
        SYNTAX  SEQUENCE OF CpqOsProcessEntry
        ACCESS  not-accessible
        STATUS  mandatory
        DESCRIPTION
            "A table of Process Entries."
        ::= { cpqOsProcess 2 }

    cpqOsProcessEntry OBJECT-TYPE
        SYNTAX  CpqOsProcessEntry
        ACCESS  not-accessible
        STATUS  mandatory
        DESCRIPTION
            "A Process Entry."
        INDEX   { cpqOsProcessIndex }
        ::= { cpqOsProcessTable 1 }

        CpqOsProcessEntry ::= SEQUENCE {
            cpqOsProcessIndex                   INTEGER,
            cpqOsProcessInstance                DisplayString,
            cpqOsProcessThreadCount             INTEGER,
            cpqOsProcessPrivateBytes            INTEGER,
            cpqOsProcessPageFileBytes           INTEGER,
            cpqOsProcessWorkingSet              INTEGER,
            cpqOsProcessCpuTimePercent          INTEGER,
            cpqOsProcessPrivilegedTimePercent   INTEGER,
            cpqOsProcessPageFaultsPerSec        INTEGER,
            cpqOsProcessCondition               INTEGER
        }

    cpqOsProcessIndex OBJECT-TYPE
        SYNTAX  INTEGER
        ACCESS  read-only
        STATUS  mandatory
        DESCRIPTION
            "The Process Instance number."
        ::= { cpqOsProcessEntry 1 }

    cpqOsProcessInstance OBJECT-TYPE
        SYNTAX  DisplayString (SIZE (0..64))
        ACCESS  read-only
        STATUS  mandatory
        DESCRIPTION
            "The Process Instance Name."
        ::= { cpqOsProcessEntry 2 }

    cpqOsProcessThreadCount OBJECT-TYPE
        SYNTAX  INTEGER
        ACCESS  read-only
        STATUS  mandatory
        DESCRIPTION
            "The number of threads currently active in this process.  An instruction
            is the basic unit of execution in a processor, and a thread is the object
            that executes instructions.  Every running process has at least one
            thread."
        ::= { cpqOsProcessEntry 3 }

    cpqOsProcessPrivateBytes OBJECT-TYPE
        SYNTAX  INTEGER
        ACCESS  read-only
        STATUS  mandatory
        DESCRIPTION
            "Private Bytes is the current number of bytes this process has allocated
            that cannot be shared with other processes."
        ::= { cpqOsProcessEntry 4 }

    cpqOsProcessPageFileBytes OBJECT-TYPE
        SYNTAX  INTEGER
        ACCESS  read-only
        STATUS  mandatory
        DESCRIPTION
            "Page File Bytes is the current number of bytes this process has used in
            the paging file(s).  Paging files are used to store pages of memory used
            by the process that are not contained in other files.  Paging files are
            shared by all processes, and lack of space in paging files can prevent
            other processes from allocating memory."
        ::= { cpqOsProcessEntry 5 }

    cpqOsProcessWorkingSet OBJECT-TYPE
        SYNTAX  INTEGER
        ACCESS  read-only
        STATUS  mandatory
        DESCRIPTION
            "Working Set is the current number of bytes in the Working Set of this
            process. The Working Set is the set of memory pages touched recently by
            the threads in the process.  If free memory in the computer is above a
            threshold, pages are left in the Working Set of a process even if they
            are not in use.  When free memory falls below a threshold, pages are
            trimmed from Working Sets.  If they are needed they will then be
            soft-faulted back into the Working Set before they leave main memory."
        ::= { cpqOsProcessEntry 6 }

    cpqOsProcessCpuTimePercent OBJECT-TYPE
        SYNTAX  INTEGER
        ACCESS  read-only
        STATUS  mandatory
        DESCRIPTION
            "% Processor Time is the percentage of elapsed time that all of the
            threads of this process used the processor to execute instructions.
            An instruction is the basic unit of execution in a computer, a thread
            is the object that executes instructions, and a process is the object
            created when a program is run.  Code executed to handle some hardware
            interrupts and trap conditions are included in this count.  On
            Multi-processor machines the maximum value of the counter is 100 % times
            the number of processors."
        ::= { cpqOsProcessEntry 7 }

    cpqOsProcessPrivilegedTimePercent OBJECT-TYPE
        SYNTAX  INTEGER
        ACCESS  read-only
        STATUS  mandatory
        DESCRIPTION
            "% Privileged Time is the percentage of elapsed time that the threads of
            the process have spent executing code in privileged mode.  When a Windows
            NT system service is called, the service will often run in Privileged Mode
            to gain access to system-private data.  Such data is protected from access
            by threads executing in user Mode.  Calls to the system can be explicit or
            implicit, such as page faults or interrupts.  Unlike some early operating
            systems, Windows NT uses process boundaries for subsystem protection in
            addition to the traditional protection of user and privileged modes.
            These subsystem processes provide additional protection.  Therefore, some
            work done by Windows NT on behalf of your application might appear in
            other subsystem processes in addition to the privileged time in your
            process."
        ::= { cpqOsProcessEntry 8 }

    cpqOsProcessPageFaultsPerSec OBJECT-TYPE
        SYNTAX  INTEGER
        ACCESS  read-only
        STATUS  mandatory
        DESCRIPTION
            "Page Faults/sec is the rate Page Faults occur in the threads executing
            in this process.  A page fault occurs when a thread refers to a virtual
            memory page that is not in its working set in main memory.  This will
            not cause the page to be fetched from disk if it is on the standby list
            and hence already in main memory, or if it is in use by another process
            with whom the page is shared."
        ::= { cpqOsProcessEntry 9 }

    cpqOsProcessCondition OBJECT-TYPE
        SYNTAX  INTEGER {
            other(1),
            ok(2),
            degraded(3),
            failed(4)
            }
        ACCESS  read-only
        STATUS  mandatory
        DESCRIPTION
            "The condition of this Process Object Instance."
        ::= { cpqOsProcessEntry 10 }


-- ****************************************************************************
--  Windows OS Mgmt. Trap Definitions
--  =================================
--
--  The SNMP trap messages must not be bigger than 484 octets (bytes).
--
--  Trap support in an SNMP agent implementation is optional.  An SNMP
--  agent implementation may support all, some, or none of the traps.
--  If traps are supported, The user should be provided with the option of
--  disabling traps.
-- **************************************************************************

    cpqOsCpuTimeDegraded TRAP-TYPE
        ENTERPRISE compaq
        VARIABLES  { sysName, cpqHoTrapFlags, cpqOsCpuIndex,
                     cpqOsCpuInstance, cpqOsCpuTimePercent }
        DESCRIPTION
            "The Processor Time performance property is set to degraded."

        --#TYPE "Processor Time Degraded (19001)"
        --#SUMMARY "The Processor performance Instance, %s is degraded with Processor Time of %d percent."
        --#ARGUMENTS {3, 4}
        --#SEVERITY MAJOR
        --#TIMEINDEX 99
        --#STATE   DEGRADED

        ::= 19001

    cpqOsCpuTimeFailed TRAP-TYPE
        ENTERPRISE compaq
        VARIABLES  { sysName, cpqHoTrapFlags, cpqOsCpuIndex,
                     cpqOsCpuInstance, cpqOsCpuTimePercent }
        DESCRIPTION
            "The Processor Time performance property is set to critical."

        --#TYPE "Processor Time Failed (19002)"
        --#SUMMARY "The Processor performance Instance, %s is critical with Processor Time of %d percent."
        --#ARGUMENTS {3, 4}
        --#SEVERITY CRITICAL
        --#TIMEINDEX 99
        --#STATE   DEGRADED

        ::= 19002

    cpqOsCacheCopyReadHitsDegraded TRAP-TYPE
        ENTERPRISE compaq
        VARIABLES  { sysName, cpqHoTrapFlags, cpqOsCacheIndex,
                     cpqOsCacheInstance, cpqOsCacheCopyReadHitsPercent}
        DESCRIPTION
            "The Cache CopyReadHits performance property is set to degraded."

        --#TYPE "Cache CopyReadHits Degraded (19003)"
        --#SUMMARY "The Cache performance property is degraded with CopyReadHits of %d percent."
        --#ARGUMENTS {4}
        --#SEVERITY MAJOR
        --#TIMEINDEX 99
        --#STATE   DEGRADED

        ::= 19003

    cpqOsCacheCopyReadHitsFailed TRAP-TYPE
        ENTERPRISE compaq
        VARIABLES  { sysName, cpqHoTrapFlags, cpqOsCacheIndex,
                     cpqOsCacheInstance, cpqOsCacheCopyReadHitsPercent}
        DESCRIPTION
            "The Cache CopyReadHits performance property is set to critical."

        --#TYPE "Cache CopyReadHits Failed (19004)"
        --#SUMMARY "The Cache performance property is critical with CopyReadHits of %d percent."
        --#ARGUMENTS {4}
        --#SEVERITY CRITICAL
        --#TIMEINDEX 99
        --#STATE   DEGRADED

        ::= 19004

    cpqOsPageFileUsageDegraded TRAP-TYPE
        ENTERPRISE compaq
        VARIABLES  { sysName, cpqHoTrapFlags, cpqOsPagingFileIndex,
                     cpqOsPagingFileInstance, cpqOsPageFileUsagePercent }
        DESCRIPTION
            "The PagingFile Usage performance property is set to degraded."

        --#TYPE "PagingFile Usage Degraded (19005)"
        --#SUMMARY "The PagingFile performance instance, %s is degraded with PagingFile Usage of %d percent."
        --#ARGUMENTS {3, 4}
        --#SEVERITY MAJOR
        --#TIMEINDEX 99
        --#STATE   DEGRADED

        ::= 19005

    cpqOsPageFileUsageFailed TRAP-TYPE
        ENTERPRISE compaq
        VARIABLES  { sysName, cpqHoTrapFlags, cpqOsPagingFileIndex,
                     cpqOsPagingFileInstance, cpqOsPageFileUsagePercent }
        DESCRIPTION
            "The PagingFile Usage performance property is set to critical."

        --#TYPE "PagingFile Usage Failed (19006)"
        --#SUMMARY "The PagingFile performance instance, %s is critical with PagingFile Usage of %d percent."
        --#ARGUMENTS {3, 4}
        --#SEVERITY CRITICAL
        --#TIMEINDEX 99
        --#STATE   DEGRADED

        ::= 19006

    cpqOsLogicalDiskBusyTimeDegraded TRAP-TYPE
        ENTERPRISE compaq
        VARIABLES  { sysName, cpqHoTrapFlags, cpqOsLogicalDiskIndex,
                     cpqOsLogicalDiskInstance, cpqOsLogicalDiskBusyTimePercent }
        DESCRIPTION
            "The LogicalDisk BusyTime performance property is set to degraded."

        --#TYPE "LogicalDisk BusyTime Degraded (19007)"
        --#SUMMARY "The LogicalDisk performance instance, %s is degraded with DiskBusyTime of %d percent."
        --#ARGUMENTS {3, 4}
        --#SEVERITY MAJOR
        --#TIMEINDEX 99
        --#STATE   DEGRADED

        ::= 19007

    cpqOsLogicalDiskBusyTimeFailed TRAP-TYPE
        ENTERPRISE compaq
        VARIABLES  { sysName, cpqHoTrapFlags, cpqOsLogicalDiskIndex,
                     cpqOsLogicalDiskInstance, cpqOsLogicalDiskBusyTimePercent }
        DESCRIPTION
            "The LogicalDisk BusyTime performance property is set to critical."

        --#TYPE "LogicalDisk BusyTime Failed (19008)"
        --#SUMMARY "The LogicalDisk performance instance, %s is critical with DiskBusyTime of %d percent."
        --#ARGUMENTS {3, 4}
        --#SEVERITY CRITICAL
        --#TIMEINDEX 99
        --#STATE   DEGRADED

        ::= 19008

END
